module vlan-fabric-ce-adapter {

    yang-version 1;
    namespace "urn:opendaylight:params:xml:ns:yang:controller:config:fabric:vlan:adapter:ce";
    prefix "ce-adapter";

    import config { prefix config; revision-date 2013-04-05; }
    import opendaylight-md-sal-binding { prefix mdsal; revision-date 2013-10-28; }

    revision "2016-06-30" {
        description "initial revision.";
    }

    // This is the definition of the service implementation as a module identity.
    identity vlan-fabric-ce-adapter {
        base config:module-type;

        // Specifies the prefix for generated java classes.
        config:java-name-prefix VlanFabricCEAdapter;
    }

	//
    identity ce-connector {
    	base config:module-type;
    	
    	config:java-name-prefix CEConnector;
    }

	// Augment the 'configuration' choice node under modules/module.
    augment "/config:modules/config:module/config:configuration" {
        case ce-connector {
            when "/config:modules/config:module/config:type = 'ce-connector'";

            container data-broker {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }

			container connection-info {
				leaf management-ip {
					type string;
				}
				leaf logon-user {
					type string;
				}
				leaf password {
					type string;
				}
			}
        }
    }

    // Augment the 'configuration' choice node under modules/module.
    augment "/config:modules/config:module/config:configuration" {
        case vlan-fabric-ce-adapter {
            when "/config:modules/config:module/config:type = 'vlan-fabric-ce-adapter'";

            container data-broker {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }
        }
    }
}
